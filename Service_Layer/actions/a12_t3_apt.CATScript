Language = "VBSCRIPT"

' Genera el codigo APT
' Ejecutar macro con CATProcess activo

' Fuente original:
' http://catiadoc.free.fr/online/CAAScdBase/CAAMaiScriptHome.htm


Sub CATMain()

	Dim MfgDoc1 As Document
	Set MfgDoc1 = CATIA.ActiveDocument
	
	Dim ActivityRef As AnyObject
	Set ActivityRef = MfgDoc1.GetItem("Process")

	Dim Setup1 As ManufacturingSetup
	If (ActivityRef.IsSubTypeOf("PhysicalActivity")) Then
		Set childs = ActivityRef.ChildrenActivities
		quantity = childs.Count
		if quantity <= 0 then
			Exit Sub
		End if
		NumberOfPO = 0
		For I=1 To quantity
			Set child = childs.Item(I)
			If (child.IsSubTypeOf("ManufacturingSetup")) Then
				Set Setup1 = child
				NumberOfPO = NumberOfPO +1
				Exit For
			End If
		Next   
	End If

	if NumberOfPO <= 0 then
	  Exit Sub
	End if

	Set ProgramList = Setup1.Programs

	Dim Program1 As ManufacturingProgram
	Set Program1 = ProgramList.GetElement(1)


' A partir de aquí se siguen las instrucciones del manual:
' http://catiadoc.free.fr/online/CAAScdMaiTechArticles/CAAMaiTocManufacturingActivity.htm
' Se pretende generar el código a partir de Program1

	
'The ManufacturingOutputGenerator object can be retrieved using the GetItem method called onto the ManufacturingActivity object as follows:
'
'Dim activity As ManufacturingActivity
'...
'Dim outputGen As ManufacturingOutputGenerator
'Set outputGen = activity.GetItem("ManufacturingOutputGenerator")

	
	Dim outputGen As ManufacturingOutputGenerator
	Set outputGen = Program1.GetItem("ManufacturingOutputGenerator")

	
'The ManufacturingGeneratorData is created and retrieved from either the ManufacturingOutputGenerator object or from its derived object ManufacturingAptGenerator using the InitFileGenerator method as follows:
'
'Dim outputGen As ManufacturingOutputGenerator
'...
'Dim format, fileName As String
'format = "APT"
'fileName = "c:\myFile.txt"
'Dim genData As ManufacturingGeneratorData
'outputGen.InitFileGenerator(format, fileName, genData)


	Dim format, filename As String
	format = "APT"
'	fileName = "c:\zzz.aptsource"
	filename = CATIA.FileSelectionBox("Generación Documento APT", "*.aptsource", CatFileSelectionModeSave)
	Dim genData As ManufacturingGeneratorData
	outputGen.InitFileGenerator format, filename, genData
	
	' PROBLEMA
	' El código no se guarda al archivo especificado.
	' Tampoco con este método (se supone innecesario, ya lo genera InitFileGenerator):
	outputGen.GenerateOutputCode(genData)


'In the same way, the ManufacturingOutput object can be retrieved using the GetOutputStream method called onto the ManufacturingGeneratorData object:
'
'Dim genData As ManufacturingGeneratorData
'...
'Dim outputStream As ManufacturingOutput
'genData.GetOutputStream(outputStream)

	
	Dim outputStream As ManufacturingOutput
	genData.GetOutputStream(outputStream)

	' PROBLEMA
	' Al ajecutarse esta macro se obtiene un error ScriptingERR_1002
	' con la descripción: Se requiere un objeto 'genData'.
	
	
End Sub
